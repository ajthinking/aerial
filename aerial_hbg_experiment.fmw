FME workspace aerial_hbg_experiment.fmw

Parameters:
- SourceDataset_PNGRASTER = $(FME_MF_DIR)0001TP_006690.png   # Source PNG (Portable Network Graphics) File(s)
- SourceDataset_PNGRASTER_3 = $(FME_MF_DIR)0001TP_006690_P.png   # Source PNG (Portable Network Graphics) File(s)
- SourceDataset_TIFF = $(FME_MF_DIR)6215_100.tif   # Source TIFF (Tagged Image File Format) File(s)
- SourceDataset_GEOJSON = /Users/anders/Downloads/flygbilder.json   # Source GeoJSON File or URL
- SourceDataset_GEOJSON_7 = $(FME_MF_DIR)MAPBUILDING_6215_100.geojson   # Source GeoJSON File or URL
- SourceDataset_GEOJSON_4 = /Users/anders/Downloads/baskarta/Transport.MAPROADEDGE.geojson   # Source GeoJSON File or URL
- DestDataset_GEOJSON = $(FME_MF_DIR)MAPROADEDGE_6215_100.geojson   # Destination GeoJSON File
- SourceDataset_GEOJSON_6 = $(FME_MF_DIR)MAPROADEDGE_6215_100.geojson   # Source GeoJSON File or URL

Readers:
- PNGRASTER_1: PNGRASTER from $(SourceDataset_PNGRASTER)
- PNGRASTER_2: PNGRASTER from $(SourceDataset_PNGRASTER_3)
- TIFF_1: TIFF from $(SourceDataset_TIFF) in EPSG:3008
- GEOJSON_1: GEOJSON from $(SourceDataset_GEOJSON)
- GEOJSON_2: GEOJSON from $(SourceDataset_GEOJSON_7)
- GEOJSON_3: GEOJSON from $(SourceDataset_GEOJSON_4)
- GEOJSON_5: GEOJSON from $(SourceDataset_GEOJSON_6)

Writers:
- GEOJSON_4: GEOJSON to $(DestDataset_GEOJSON)

MAPBUILDING (reader GEOJSON_2)
    attributes: EASEMENTBUILDING_resolved string, ORIGINHEIGHT_resolved string, ONGROUND_resolved string, EXEMPTADDRESSING_resolved string, MEASUREMETHOD_resolved string, FITTED_resolved string, SUPPLIER_resolved string, BALSTATUS_resolved string, SRSORIGINPLAN_resolved string, STATUS_resolved string, ORIGINPLAN_resolved string, LIESONUUID string, NONFREEHOLDPROPERTY_resolved string, SRSORIGINHEIGHT_resolved string, UNCERTAINUSE_resolved string, geodb_subtype_name string, ISMAINBUILDING_resolved string, BELONGSTOUUID string, PURPOSE_resolved string, BUILDINGNAMETYPE_resolved string, geodb_oid int, BUILDINGREMARKTYPE_resolved string, AFFECTEDBYUUID string, geodb_type string, ACCURACYHEIGHT string, ACCURACYPLAN string, ALTITUDE string, COMMENTARY string, DTYPE string, EXTERNALID int,
      FITTED int, GID string, MODIFICATIONDATE string, NAME string, OBJECTID int, REGDATE string, SCALE string, STATUS int, STYPE int, BALSTATUS int, Shape.STArea() float, LIESON int, SYNCDATE string, PURPOSE int, UNCERTAINUSE int, ADDRESS string, HOUSENUMBER string, CONSTRUCTIONYEAR string, PLACENAMEID string, ISMAINBUILDING int, NONFREEHOLDPROPERTY int, EXEMPTADDRESSING int, EASEMENTBUILDING int, Shape.STLength() float, EXTENSIONYEAR string, BUILDINGSID string, geodb_feature_dataset string, USEFULFLOORSPACE int, BUILDINGNAMETYPE int, AFFECTEDBY int,
      SRSORIGINHEIGHT int, SRSORIGINPLAN int, SUPPLIER int, ONGROUND int, ORIGINPLAN int, MEASUREMETHOD int, ORIGINHEIGHT int
    -> Reprojector
Reprojector
    DEST = EPSG:3008
    INTERPOLATION_TYPE_NAME = Nearest Neighbor
    RASTER_CELL_SIZE = Preserve Cells
    RASTER_TOLERANCE = 0.0
    SOURCE = Read from feature
    REPROJECTED -> Clipper_2 [CLIPPER]
    REPROJECTED -> BUILDINGS
BUILDINGS: Inspector
TIFF (reader TIFF_1)
    -> RasterGeoreferencer
RasterGeoreferencer
    POINTANDANGLE_OR_EXTENTS = Extents
    X_LL_COORD = 100000
    X_LR_COORD = 101000
    X_UL_COORD = 100000
    X_UR_COORD = 101000
    Y_LL_COORD = 6215000
    Y_LR_COORD = 6215000
    Y_UL_COORD = 6216000
    Y_UR_COORD = 6216000
    -> RasterInterpretationCoercer
    -> AERIAL
AERIAL: Inspector
Note: CREATING THE LABELS IMAGE (GRAY8)
RasterInterpretationCoercer
    COLOR_TO_COLOR = Cast
    FLOAT_TO_INTEGER = Round
    INTERPRETATION = Gray8
    NUMERIC_TO_COLOR = Cast
    -> RasterBandNodataSetter
RasterBandNodataSetter
    NODATA_VALUE = 99
    REPLACE_CELL_VALUES = No
    -> Clipper_2 [CLIPPEE]
Clipper_2
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> RasterCellValueReplacer
    OUTSIDE -> Clipper_3 [CLIPPEE]
Note: BUILDING = 0
RasterCellValueReplacer
    NEW_VALUE = 0
    REPLACE_GREATER_THAN = 0
    REPLACE_LESS_THAN = 999999999999
    REPLACE_NODATA = No
    -> RasterMosaicker
    -> R_BUILDING
R_BUILDING: Inspector
MAPROADEDGE (reader GEOJSON_5)
    attributes: SRSORIGINPLAN_resolved string, SUPPLIER_resolved string, LINKTYPE_resolved string, geodb_oid int, SRSORIGINHEIGHT_resolved string, MATERIAL_resolved string, HASCURB_resolved string, FITTED_resolved string, geodb_type string, STATUS_resolved string, LOCATIONMETHOD_resolved string, ORIGINPLAN_resolved string, geodb_subtype_name string, ORIGINHEIGHT_resolved string, ACCURACYHEIGHT string, ACCURACYPLAN string, ALTITUDE string, COMMENTARY string, DTYPE string, FITTED int, GID string, MODIFICATIONDATE string, OBJECTID int, ORIGINHEIGHT int, ORIGINPLAN int, REGDATE string, SCALE string, SRSORIGINHEIGHT int, SRSORIGINPLAN int, STATUS int,
      STYPE int, SUPPLIER int, LINKTYPE int, MATERIAL int, LOCATIONMETHOD int, Shape.STLength() float, HASCURB int, geodb_feature_dataset string
    -> Reprojector_3
Reprojector_3
    DEST = EPSG:3008
    INTERPOLATION_TYPE_NAME = Nearest Neighbor
    RASTER_CELL_SIZE = Preserve Cells
    RASTER_TOLERANCE = 0.0
    SOURCE = Read from feature
    REPROJECTED -> Bufferer
Bufferer
    ANGLE = 22.5
    CAP_STYLE = Round
    CORNER_STYLE = Round
    MODE = AREA
    OFFSET = 5
    BUFFERED -> Clipper_3 [CLIPPER]
    BUFFERED -> ROADS
ROADS: Inspector
Clipper_3
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> RasterCellValueReplacer_2
    OUTSIDE -> RasterCellValueReplacer_3
Note: ROAD = 1
RasterCellValueReplacer_2
    NEW_VALUE = 1
    REPLACE_GREATER_THAN = 0
    REPLACE_LESS_THAN = 999999999999
    REPLACE_NODATA = No
    -> RasterMosaicker
    -> R_ROAD
R_ROAD: Inspector
Note: DEFAULT = 2
RasterCellValueReplacer_3
    NEW_VALUE = 2
    REPLACE_GREATER_THAN = 0
    REPLACE_LESS_THAN = 999999999999
    REPLACE_NODATA = No
    -> RasterMosaicker
    -> R_DEFAULT
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> LANDUSE
LANDUSE: Inspector
R_DEFAULT: Inspector

Bookmark: EXAMPLE DATA STRUCTURE
Note: IMAGE
PNGRASTER (reader PNGRASTER_1) [off]
    -> PNGRASTER
PNGRASTER: Inspector
Note: LABELS
PNGRASTER (reader PNGRASTER_2) [off]
    -> LABELS
LABELS: Inspector

Bookmark: SAMPLE MAPROADEDGE
MAPROADEDGE (reader GEOJSON_3) [off]
    attributes: SRSORIGINPLAN_resolved string, SUPPLIER_resolved string, LINKTYPE_resolved string, geodb_oid int, SRSORIGINHEIGHT_resolved string, MATERIAL_resolved string, HASCURB_resolved string, FITTED_resolved string, geodb_type string, STATUS_resolved string, LOCATIONMETHOD_resolved string, ORIGINPLAN_resolved string, geodb_subtype_name string, ORIGINHEIGHT_resolved string, ACCURACYHEIGHT string, ACCURACYPLAN string, ALTITUDE string, COMMENTARY string, DTYPE string, FITTED int, GID string, MODIFICATIONDATE string, OBJECTID int, ORIGINHEIGHT int, ORIGINPLAN int, REGDATE string, SCALE string, SRSORIGINHEIGHT int, SRSORIGINPLAN int, STATUS int,
      STYPE int, SUPPLIER int, LINKTYPE int, MATERIAL int, LOCATIONMETHOD int, Shape.STLength() float, HASCURB int, geodb_feature_dataset string
    -> Reprojector_2
Reprojector_2
    DEST = EPSG:3008
    INTERPOLATION_TYPE_NAME = Nearest Neighbor
    RASTER_CELL_SIZE = Preserve Cells
    RASTER_TOLERANCE = 0.0
    SOURCE = Read from feature
    REPROJECTED -> Clipper [CLIPPEE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> MAPROADEDGE (writer GEOJSON_4)
MAPROADEDGE (writer GEOJSON_4)
    attributes: multi_reader_full_id int, multi_reader_type string, SRSORIGINPLAN_resolved string, SUPPLIER_resolved string, LINKTYPE_resolved string, geodb_oid int, SRSORIGINHEIGHT_resolved string, MATERIAL_resolved string, HASCURB_resolved string, FITTED_resolved string, multi_reader_id int, geodb_type string, STATUS_resolved string, LOCATIONMETHOD_resolved string, multi_reader_keyword string, ORIGINPLAN_resolved string, geodb_subtype_name string, ORIGINHEIGHT_resolved string, ACCURACYHEIGHT string, ACCURACYPLAN string, ALTITUDE string, COMMENTARY string, DTYPE string, FITTED int, GID string, MODIFICATIONDATE string, OBJECTID int, ORIGINHEIGHT int, ORIGINPLAN int, REGDATE string,
      SCALE string, SRSORIGINHEIGHT int, SRSORIGINPLAN int, STATUS int, STYPE int, SUPPLIER int, LINKTYPE int, MATERIAL int, LOCATIONMETHOD int, Shape.STLength() float, HASCURB int, geodb_feature_dataset string
